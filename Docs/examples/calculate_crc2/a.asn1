MYMODULE DEFINITIONS ::= BEGIN

PacketHeader ::= SEQUENCE
{
    version	INTEGER(1..100),
    release	INTEGER(1..100),
    varSizeArray	SEQUENCE (SIZE(1..20)) OF INTEGER (1..20)
}


PacketBody ::= CHOICE
{
    aReal  				REAL,
    anInteger  			INTEGER (0 .. 65535),
    anotherSizeArray	SEQUENCE (SIZE (1..100)) OF INTEGER (1..200)
}

Packet ::= SEQUENCE {
	p-header PacketHeader,
    p-body   PacketBody
}

END
