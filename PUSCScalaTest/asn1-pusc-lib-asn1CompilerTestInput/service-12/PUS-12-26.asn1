--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-12-26 DEFINITIONS AUTOMATIC TAGS ::= BEGIN
EXPORTS ALL;
IMPORTS
    FMON-ID, FMON-ProtectionStatus, FMON-Status FROM FMON
    CheckValidityCondition FROM CheckValidityCondition
    EventDefinition-ID FROM EventDefinition
    Min-PMON-FailingNumber FROM PMON-FailingNumber
    PUSC-UINT32 FROM BasicTypes
    PMON-ID FROM PMON;

maxTM-12-26-MonitoringDefinitionCount INTEGER ::= 4095
maxTM-12-26-PMON-ID-Count INTEGER ::= 4095

TM-12-28-FunctionalMonitoringDefinitionReport ::= SEQUENCE
{
--! n1 UnsignedInteger,
    report SEQUENCE (SIZE(1 .. 4095)) OF TM-12-28-MonitoringDefinitionReport
}

TM-12-28-MonitoringDefinitionReport ::= TM-12-28-MonitoringDefinitionReportGeneric
{FMON-ID, CheckValidityCondition, EventDefinition-ID, Min-PMON-FailingNumber, PMON-ID}
(WITH COMPONENTS
{
    checkValidityCondition PRESENT,
    fmonProtectionStatus PRESENT,
    min-PMON-FailingNumber PRESENT
})

TM-12-28-MonitoringDefinitionReportGeneric
{FMON-ID-Type, CheckValidityConditionType, EventDefinition-ID-Type, Min-PMON-FailingNumberType, PMON-ID-Type} ::= SEQUENCE
{
    fmon-ID FMON-ID-Type,
    checkValidityCondition CheckValidityCondition OPTIONAL,
    fmonProtectionStatus FMON-ProtectionStatus OPTIONAL,
    fmonStatus FMON-Status,
    min-PMON-FailingNumber Min-PMON-FailingNumberType OPTIONAL,
--! n2 UnsignedInteger,
    pmon-ID SEQUENCE (SIZE(1 .. maxTM-12-26-PMON-ID-Count)) OF PMON-ID-Type
}

END
