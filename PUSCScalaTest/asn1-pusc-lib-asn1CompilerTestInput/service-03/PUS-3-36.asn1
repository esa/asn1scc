--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-3-36 DEFINITIONS AUTOMATIC TAGS ::= BEGIN
EXPORTS ALL;
IMPORTS
    DiagnosticParameterReportStructure-ID FROM DiagnosticParameterReportStructure
    PeriodicGenerationActionStatus FROM PeriodicGenerationActionStatus
    CollectionInterval FROM CollectionInterval
    PUSC-UINT32 FROM BasicTypes
    PeriodicGenerationProperties-Generic FROM PeriodicGenerationProperties;

maxTM-3-36-PeriodicGenerationProperties INTEGER ::= 63

TM-3-36-DiagnosticParameterReportPeriodicGenerationPropertiesReport ::= SEQUENCE
{
--! n UnsignedInteger, moved to acn
    periodicGenerationProperties SEQUENCE (SIZE(1 .. maxTM-3-36-PeriodicGenerationProperties)) OF DiagnosticPeriodicGenerationProperties
}

DiagnosticPeriodicGenerationProperties
  ::= PeriodicGenerationProperties-Generic
    {DiagnosticParameterReportStructure-ID, PeriodicGenerationActionStatus, CollectionInterval}

END
