--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

HousekeepingParameterReportForwardControl DEFINITIONS AUTOMATIC TAGS ::= BEGIN
EXPORTS ALL;
IMPORTS
    ApplicationProcess-ID FROM ApplicationProcess
    PUSC-UINT32 FROM BasicTypes
    SubsamplingRate FROM SubsamplingRate
    HousekeepingParameterReportStructure-ID FROM HousekeepingParameterReportStructure;

maxHousekeepingParameterReportForwardControlCount INTEGER ::= 31
maxHousekeepingStructure-ID-Count INTEGER ::= 31

HousekeepingParameterReportForwardControlSubsampling ::= HousekeepingParameterReportForwardControlGeneric
{SingleHousekeepingParameterReportForwardControlSubsampling}

HousekeepingParameterReportForwardControlNoSubsampling ::= HousekeepingParameterReportForwardControlGeneric
{SingleHousekeepingParameterReportForwardControlNoSubsampling}

SingleHousekeepingParameterReportForwardControlSubsampling ::= SingleHousekeepingParameterReportForwardControlGeneric
{ApplicationProcess-ID, HousekeepingParameterStructure-ID-ConfigurationSubsampling}

SingleHousekeepingParameterReportForwardControlNoSubsampling ::= SingleHousekeepingParameterReportForwardControlGeneric
{ApplicationProcess-ID, HousekeepingParameterStructure-ID-ConfigurationNoSubsampling}

HousekeepingParameterStructure-ID-ConfigurationNoSubsampling ::= HousekeepingParameterStructure-ID-ConfigurationGeneric
{HousekeepingParameterReportStructure-ID, NULL}
(WITH COMPONENTS
{
    subsamplingRate ABSENT
})

HousekeepingParameterStructure-ID-ConfigurationSubsampling ::= HousekeepingParameterStructure-ID-ConfigurationGeneric
{HousekeepingParameterReportStructure-ID, NULL}
(WITH COMPONENTS
{
    subsamplingRate PRESENT
})

HousekeepingParameterReportForwardControlGeneric {SingleHousekeepingParameterReportForwardControlType} ::= SEQUENCE
{
--! n1 UnsignedInteger,
    forwardControl SEQUENCE (SIZE(1 .. maxHousekeepingParameterReportForwardControlCount)) OF SingleHousekeepingParameterReportForwardControlType
}

SingleHousekeepingParameterReportForwardControlGeneric {ApplicationProcess-ID-Type, HousekeepingParameterStructure-ID-Type} ::= SEQUENCE
{
    applicationProcess-ID ApplicationProcess-ID-Type,
--! n2 UnsignedInteger,
    structure SEQUENCE (SIZE(0 .. maxHousekeepingStructure-ID-Count)) OF type HousekeepingParameterStructure-ID-Type
}

HousekeepingParameterStructure-ID-ConfigurationGeneric {HousekeepingParameterStructure-ID-Type, SubsamplingRateType} ::= SEQUENCE
{
    id HousekeepingParameterStructure-ID-Type,
    subsamplingRate SubsamplingRateType OPTIONAL
}


END
