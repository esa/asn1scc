--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PacketTypes DEFINITIONS AUTOMATIC TAGS::= BEGIN
EXPORTS ALL;
IMPORTS
    ApplicationProcess-ID FROM ApplicationProcess;

CCSDS-Packet {Packet-ID-Type, PacketDataField-Type} ::= SEQUENCE
{
    packetVersionNumber PacketVersionNumberValue,
    packet-ID Packet-ID-Type,
    packetSequenceControl PacketSequenceControl,
    packetDataLength PacketDataLength,
    packetDataField PacketDataField-Type
}

PacketVersionNumberValue ::= NULL

Packet-ID {PacketType-Type} ::= SEQUENCE
{
    packetType PacketType-Type,
--! secondaryHeaderFlag INTEGER (0 .. 1),  moved to ACN
    applicationProcess-ID ApplicationProcess-ID
}

SecondaryHeaderFlag ::= INTEGER (0 .. 6)

PacketSequenceControl ::= SEQUENCE
{
    sequenceFlags NULL,
    packetSequenceCountOrName INTEGER (0 .. 16383)
}

PacketDataLength ::= INTEGER (0 .. 65535)

PacketDataField {PacketDataWithSecondaryHeader-Type, PacketDataNoSecondaryHeader-Type} ::= CHOICE
{
    dataWithSecondaryHeader PacketDataWithSecondaryHeader-Type,
    dataNoSecondaryHeader PacketDataNoSecondaryHeader-Type
}

DataWithSecondaryHeader {SecondaryHeaderField-Type, Payload-Type} ::= SEQUENCE
{
    secondaryHeader SecondaryHeaderField-Type,
    data Payload-Type,
--! spare NULL,    defined as align-to-next acn encoding
    packetErrorControl PacketErrorControl OPTIONAL
}

DataNoSecondaryHeader {Payload-Type} ::= SEQUENCE
{
    data Payload-Type,
--! spare NULL,    defined as align-to-next acn encoding
    packetErrorControl PacketErrorControl OPTIONAL
}

PacketErrorControl ::= BIT STRING (SIZE(16))

END
