TEST-CASE DEFINITIONS AUTOMATIC TAGS::= BEGIN

	MyPDU ::= IA5String(SIZE(20))(FROM("A".."Z"|"a".."z"|" "))
	pdu1 MyPDU ::= "George Mamais       "
	
END

-- ASCII encodings
--TCLFC    MyPDU[encoding ASCII, size null-terminated, termination-pattern '41'H]               $$$ sample1.acn:4:45: error: The termination-pattern defines a character which belongs to the allowed values of the ASN.1 type. Use another value in the termination-pattern or apply different constraints in the ASN.1 type.
--TCLS     MyPDU[encoding ASCII, size null-terminated, termination-pattern '01'H]
--TCLS     MyPDU[encoding ASCII, size null-terminated, termination-pattern '00000001'B]
--TCLS     MyPDU[encoding ASCII, size 20]
--TCLS     MyPDU[encoding ASCII, size null-terminated]

-- char index encodings
--TCLS     MyPDU[]
--TCLS     MyPDU[size 20]
