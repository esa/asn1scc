TEST-CASE  DEFINITIONS AUTOMATIC TAGS::= BEGIN

	MyPDU ::= SEQUENCE {
		int1	INTEGER(0..15),
		int2	INTEGER(0..65535) OPTIONAL,
		enm		ENUMERATED {
					one(1), two(2), three(3),
					 four(4), thousand(1000)
				},
		buf	 OCTET STRING (SIZE(10)),
		gg  SEQUENCE {
			int1	INTEGER(0..15),
			int2	INTEGER(0..65535),
			enm	ENUMERATED {
					pone(1), ptwo(2), pthree(3),
					 pfour(4), pthousand(1000)
				},
			buf	[APPLICATION 104]	OCTET STRING (SIZE(10))
		}
	}
	
	pdu1 MyPDU ::= {int1 10, int2 31415, enm one, buf '00112233445566778899'H, gg {int1 10, int2 200, enm pone, buf '00112233445566778899'H }}

	
END


--TCLS     MyPDU[]  {int1[], bInt2Present BOOLEAN[], int2[encoding pos-int, size 16, present-when bInt2Present], enm[], buf[], gg[]}  
--TCLFC     MyPDU[size 200]  {int1[], bInt2Present BOOLEAN[], int2[encoding pos-int, size auto, present-when bInt2Present], enm[], buf[], gg[]}   $$$ sample1.acn:4:7: error: Acn property 'size' cannot be applied here
