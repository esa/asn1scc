TEST-CASE DEFINITIONS AUTOMATIC TAGS::= BEGIN

    
    MyPDU   ::= REAL (1 .. 5.0)

	pdu1 MyPDU ::= 3.14159265
	
END

--TCLFC     MyPDU[encoding IEEE754-1985-64, endianness little]    $$$  sample1.acn:4:6: error: Acn property 'IEEE754-1985-64' cannot be applied when -fpWordSize  4
--TCLFC     MyPDU[encoding IEEE754-1985-64, endianness big]    $$$  sample1.acn:4:6: error: Acn property 'IEEE754-1985-64' cannot be applied when -fpWordSize  4
--TCLS     MyPDU[encoding IEEE754-1985-32]
--TCLS     MyPDU[]
