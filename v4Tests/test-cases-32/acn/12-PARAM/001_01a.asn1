-- It tests the   
-- 'pdu1' does conform to its type constraints. 

TEST-CASE DEFINITIONS AUTOMATIC TAGS::= BEGIN
    
    MyPDU ::= SEQUENCE {
        tap     TAP2File
	}

    TAP2File::=SEQUENCE {
        data    SourceData
    }

    SourceData::=SEQUENCE {
        operatorID  IA5String(SIZE(1..10)),
        calls   SEQUENCE (SIZE(1..10)) OF Call
    }	

	
	CallsSize ::= INTEGER (1..10)
    Call ::= IA5String(SIZE(1..5))
    
	pdu1 MyPDU ::= {tap { data{operatorID "FA23DF", calls{"22433","23423","57437","43632"}} }}
	
END

--TCFS     001_01a.acn
