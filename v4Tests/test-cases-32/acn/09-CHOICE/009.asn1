TEST-CASE DEFINITIONS AUTOMATIC TAGS::= BEGIN

ChoiceSelector ::= ENUMERATED
{
  a1,
  a2
}

TestType ::= INTEGER(0..255)

ChoiceOne ::= CHOICE
{
  a1 TestType,
  a2 TestType
}

ChoiceTwo ::= CHOICE
{
  a1 TestType,
  a2 TestType
}

--TCLS     ChoiceSelector [size 8, encoding pos-int] TestType [size 8, encoding pos-int] ChoiceOne<ChoiceSelector:sel> [determinant sel] ChoiceTwo<ChoiceSelector:sel> [determinant sel]

END
