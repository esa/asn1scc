TEST-CASE DEFINITIONS AUTOMATIC TAGS::= BEGIN

	MyPDU ::= CHOICE {
		int1	INTEGER(0..15),
		int2	INTEGER(0..65535),
		enm		ENUMERATED {
					one(1), two(2), three(3),
					 four(4), thousand(1000)
				},
		buf	 OCTET STRING (SIZE(10)),
		gg  SEQUENCE {
			int1	INTEGER(0..15),
			int2	INTEGER(0..65535),
			enm	ENUMERATED {
					pone(1), ptwo(2), pthree(3),
					 pfour(4), pthousand(1000)
				},
			buf	[APPLICATION 104]	OCTET STRING (SIZE(10))
		}
	}
	
	pdu1 MyPDU ::= gg : {int1 10, int2 200, enm pone, buf '00112233445566778899'H }

END

--TCLFC     MyPDU[determinant tt]       $$$ sample1.acn:4:19: error: Invalid reference 'tt'
--TCLS     MyPDU[]
--TCLFC     MyPDU[determinant ]       $$$ sample1.acn:4:19: error: no viable alternative at input ']'
