TEST-CASE DEFINITIONS AUTOMATIC TAGS::= BEGIN

	MyPDU ::= INTEGER
	
	
END


--TCLS     MyPDU[encoding ASCII, size 88]  
--TCLFC    MyPDU[encoding ASCII, size 240]          $$$ sample1.acn:4:6: error: Size must be less than 88
--TCLS     MyPDU[encoding ASCII, size null-terminated]
