TEST-CASE DEFINITIONS AUTOMATIC TAGS::= BEGIN

    MyPDU ::= SEQUENCE {
        a1  INTEGER(1..200),
        a2  MySqOf
    }

	MySqOf ::= SEQUENCE (SIZE(0..20)) OF SEQUENCE {
		int1	INTEGER(0..15),
		int2	INTEGER(0..65535),
		enm		ENUMERATED {
					one(1), two(2), three(3),
					 four(4), thousand(1000)
				},
		buf	 OCTET STRING (SIZE(10)),
		gg  SEQUENCE {
			int1	INTEGER(0..15),
			int2	INTEGER(0..65535),
			enm	ENUMERATED {
					pone(1), ptwo(2), pthree(3),
					 pfour(4), pthousand(1000)
				},
			buf	[APPLICATION 104]	OCTET STRING (SIZE(10))
		} OPTIONAL
	}
	
	INT0-20 ::= INTEGER(0..20)
	
	pdu1 MyPDU ::=  {a1 1, a2 { 
							{int1 10, int2 200, enm one, buf '00112233445566778899'H}
							}}
END


--TCLS     MyPDU[] MySqOf[]
--TCLS     INT0-20[] MyPDU[]{a1[], a3 INT0-20[], a2<a3>[]} MySqOf<INT0-20:nLen>[size nLen]
