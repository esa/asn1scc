TEST-CASE DEFINITIONS AUTOMATIC TAGS::= BEGIN

	MyPDU ::= INTEGER(1|2|3|-20)
	
	pdu1 MyPDU ::= -20
    
	
END

--TCLS     MyPDU[encoding twos-complement, size 8]
--TCLS     MyPDU[encoding twos-complement, size 16]
--TCLS     MyPDU[encoding twos-complement, size 32]
--TCLS     MyPDU[encoding twos-complement, size 64]
--TCLS     MyPDU[encoding twos-complement, size 16, endianness big]
--TCLS     MyPDU[encoding twos-complement, size 32, endianness big]
--TCLS     MyPDU[encoding twos-complement, size 64, endianness big]
--TCLS     MyPDU[encoding twos-complement, size 16, endianness little]
--TCLS     MyPDU[encoding twos-complement, size 32, endianness little]
--TCLS     MyPDU[encoding twos-complement, size 64, endianness little]
