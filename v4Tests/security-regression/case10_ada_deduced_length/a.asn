TEST-CASE DEFINITIONS AUTOMATIC TAGS::= BEGIN
    Elem  ::= SEQUENCE { a INTEGER (0..255), b INTEGER (0..65535) OPTIONAL }
    EList ::= SEQUENCE (SIZE(1..20)) OF Elem
    Box   ::= SEQUENCE { list SEQUENCE (SIZE(2..5)) OF Elem }
END
