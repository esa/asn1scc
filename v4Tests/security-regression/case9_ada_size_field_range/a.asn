TEST-CASE DEFINITIONS AUTOMATIC TAGS ::= BEGIN

Inner ::= SEQUENCE { a INTEGER (0..255), b INTEGER (0..3) }
Dd ::= SEQUENCE { h INTEGER (0..255), d OCTET STRING (SIZE(0..10)) }

COctT16 ::= SEQUENCE { v OCTET STRING (CONTAINING Inner), tail INTEGER (0..15) }
COctP32 ::= SEQUENCE { v OCTET STRING (CONTAINING Inner), tail INTEGER (0..15) }
CBitT16 ::= SEQUENCE { v BIT STRING (CONTAINING Inner), tail INTEGER (0..15) }
CBitP32 ::= SEQUENCE { v BIT STRING (CONTAINING Inner), tail INTEGER (0..15) }
DedT16  ::= SEQUENCE { v OCTET STRING (CONTAINING Dd), tail INTEGER (0..15) }
DedP32  ::= SEQUENCE { v OCTET STRING (CONTAINING Dd), tail INTEGER (0..15) }
OctT16  ::= SEQUENCE { v OCTET STRING (SIZE(0..10)), tail INTEGER (0..15) }
BitT16  ::= SEQUENCE { v BIT STRING (SIZE(0..20)), tail INTEGER (0..15) }
SqOfT16 ::= SEQUENCE { v SEQUENCE (SIZE(0..5)) OF INTEGER (0..255), tail INTEGER (0..15) }
StrT16  ::= SEQUENCE { v IA5String (SIZE(0..10)), tail INTEGER (0..15) }
StrP64  ::= SEQUENCE { v IA5String (SIZE(0..10)), tail INTEGER (0..15) }

END
