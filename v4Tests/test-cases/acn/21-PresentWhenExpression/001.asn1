-- NO_AUTOMATIC_TEST_CASES
TEST-CASE  DEFINITIONS AUTOMATIC TAGS::= BEGIN

/*
Test case demonstrating the present when expression functionality (see also the 001.acn file)
Business requirement: field enm is present when int1 is less than 10 and even number or when it is within range 10..14.

The above requirement must be expressed as ASN.1 constraint. Usually, this is done with the usage of WITH COMPONENTS constraints.


*/


	MyPDU ::= SEQUENCE {
		int1	INTEGER(1..20),
		enm		ENUMERATED {
					one(1), two(2), three(3),
					 four(4), thousand(1000)
				} OPTIONAL
	} (
		WITH COMPONENTS {int1 (1 | 3 | 5 | 7 | 9 | 15..20),	enm ABSENT} |
		WITH COMPONENTS {int1 (0 | 2 | 4 | 6 | 8 | 10..14 ) ,	enm PRESENT}
	   )



END


--TCFS     001.acn
