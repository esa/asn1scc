-- NO_AUTOMATIC_TEST_CASES
TEST-CASE  DEFINITIONS AUTOMATIC TAGS::= BEGIN

	Toto ::= SEQUENCE {
	  a INTEGER (0..255),
	  b BOOLEAN OPTIONAL
	}

	Titi ::= Toto (WITH COMPONENTS { a (3), b ABSENT } | WITH COMPONENTS  {a (ALL EXCEPT 3), b PRESENT })

	

	
END


--TCLS     Toto[]
