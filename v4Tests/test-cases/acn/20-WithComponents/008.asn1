TEST-CASE DEFINITIONS AUTOMATIC TAGS ::= BEGIN 

    MySeq ::= SEQUENCE {
        id              INTEGER (0 .. 4294967295),
        subsamplingRate NULL  OPTIONAL
    } (WITH COMPONENTS{subsamplingRate  PRESENT})


END

--TCLS     MySeq[]
