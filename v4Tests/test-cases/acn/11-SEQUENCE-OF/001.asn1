TEST-CASE DEFINITIONS AUTOMATIC TAGS::= BEGIN


	MyPDU ::= SEQUENCE (SIZE(0..20)) OF SEQUENCE {
		int1	INTEGER(0..15),
		int2	INTEGER(0..65535),
		enm		ENUMERATED {
					one(1), two(2), three(3),
					 four(4), thousand(1000)
				},
		buf	 OCTET STRING (SIZE(10)),
		gg  SEQUENCE {
			int1	INTEGER(0..15),
			int2	INTEGER(0..65535),
			enm	ENUMERATED {
					pone(1), ptwo(2), pthree(3),
					 pfour(4), pthousand(1000)
				},
			buf	[APPLICATION 104]	OCTET STRING (SIZE(10))
		} OPTIONAL
	}
	
	pdu1 MyPDU ::=  { 
							{int1 10, int2 200, enm one, buf '00112233445566778899'H}
							}
END


--TCLFC    MyPDU[size 20]       $$$ sample1.acn:4:6: error: The size constraints of the ASN.1  allows variable items (0 .. 20). Therefore, you should either remove the size property (in which case the size determinant will be encoded automatically exactly like uPER), or use a an Integer field as size determinant
--TCLFC     MyPDU[] {dummy[], dummy2[] }   $$$ sample1.acn:4:10: error: dummy2 Unexpected field name
--TCLS     MyPDU[] 
--TCLS     MyPDU[] {[] }
