-- KNOWN_FAILURE(Rust): the Rust validator compares a value-constrained BIT STRING with bit_string_equal, which is FALSE when the value array (capacity) and the constant array differ in length, so every value of Allowed is rejected
-- BIT STRING lengths in values: the length of a variable-size BIT STRING value is
-- its number of bits, in a value assignment (C wrote the number of bytes: 2 instead of 10, below SIZE(4..20)) and in
-- the automatic test values of a value-constrained BIT STRING (both languages wrote the minimum size, 1).

TEST-CASE DEFINITIONS AUTOMATIC TAGS::= BEGIN

    Bits     ::= BIT STRING (SIZE(4..20))
    Allowed  ::= BIT STRING (SIZE(1..20)) ('1010'B | '11'B | '110011001'B)

    MyPDU ::= SEQUENCE {
        b  Bits,
        a  Allowed
    }

    bv   Bits  ::= '1010101010'B
    pdu1 MyPDU ::= {b '110011001100'B, a '110011001'B}

END

--TCLS     MyPDU[]
--TCLS     MyPDU[] {len INTEGER [size 5, encoding pos-int], b[size len], a[]}
