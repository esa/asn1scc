TEST-CASE  DEFINITIONS AUTOMATIC TAGS::= BEGIN

	MyPDU ::= SEQUENCE {
            a INTEGER,
            b NULL,
            c NumericString(SIZE(2))
	}
	
	pdu1 MyPDU ::= {a 1, b NULL, c "42"}
--TCLS     MyPDU[] {a[], b[], c[]}
--TCLFC    MyPDU[] {a[], b[]}  $$$ sample1.acn:4:6: error: No ACN encoding specification was provided for component c

END
