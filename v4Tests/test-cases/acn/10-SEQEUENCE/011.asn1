TEST-CASE  DEFINITIONS AUTOMATIC TAGS::= BEGIN

	MyPDU ::= SEQUENCE {
		gmamais-myInt	MyInt
	}
    MyInt   ::= INTEGER
	

	
END


--TCLFC     MyPDU[]         $$$ sample1.asn1:4:2: error: component name 'gmamais-myInt' conflicts with type assignment 'MyInt'. May cause compilation errors in case insensitive languages
