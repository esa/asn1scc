-- NOCOVERAGE (Ada): the "when T_Thing_field1_PRESENT" arms of the ALWAYS ABSENT alternative are never executed
-- 'size deduced' before a CHOICE with an ALWAYS ABSENT alternative: the front end counted the absent alternative in
-- the index width (2 bits instead of 1), so the decoder of 'data' reserved 10 bits for 'tail' instead of 9 and
-- counted one octet too few whenever the stream had no bit to spare.

TEST-CASE DEFINITIONS AUTOMATIC TAGS::= BEGIN

    T-UInt8    ::= INTEGER (0..255)
    T-Thing    ::= CHOICE { field1 T-UInt8, field2 T-UInt8, field3 T-UInt8 }
    T-SubThing ::= T-Thing (WITH COMPONENTS {field1 ABSENT})
    Bytes      ::= OCTET STRING (SIZE(0..10))

    Pdu ::= SEQUENCE {
        data  Bytes,
        tail  T-SubThing
    }

END

--TCLS     Pdu[] {data[size deduced], tail[]}
