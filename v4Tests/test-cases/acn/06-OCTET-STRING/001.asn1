-- RUN_SPARK
TEST-CASE DEFINITIONS AUTOMATIC TAGS::= BEGIN

	MyPDU ::= OCTET STRING (SIZE(1..20))
	
	pdu1 MyPDU ::= 'AFBC4583'H
	
END


--TCLFC    MyPDU[size 20]               $$$ sample1.acn:4:6: error: The size constraints of the ASN.1  allows variable items (1 .. 20). Therefore, you should either remove the size property (in which case the size determinant will be encoded automatically exactly like uPER), or use a an Integer field as size determinant
--TCLS     MyPDU[]
