-- RUN_SPARK
TEST-CASE DEFINITIONS AUTOMATIC TAGS::= BEGIN

	MyPDU ::= SEQUENCE {
        a2 OCTET STRING (SIZE(MyRange))
    }
	MyRange::= INTEGER(1..20)
	pdu1 MyPDU ::= {a2 'AFBC4583'H}
	
END


--TCLS     MyRange[encoding pos-int, size 5] MyPDU[] {a1 MyRange[], a2[size a1] }
--TCLS     MyRange[encoding pos-int, size 8] MyPDU[] {a11 MyRange[], a2[size a11] }
--TCLFC     MyRange[encoding twos-complement, size 6] MyPDU[] {a11 MyRange[], a2[size a11] }   $$$ sample1.acn:4:8: error: Acn property twos-complement cannot be applied to non negative INTEGER types
--TCLS     MyPDU[] {a11 MyRange[], a2[size a11] }
--TCLS     MyPDU[]
--TCLFC    MyPDU[] {a1 MyRange[], a2[size 20]}              $$$ sample1.acn:4:26: error: The size constraints of the ASN.1  allows variable items (1 .. 20). Therefore, you should either remove the size property (in which case the size determinant will be encoded automatically exactly like uPER), or use a an Integer field as size determinant
