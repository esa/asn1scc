-- RUN_SPARK
TEST-CASE DEFINITIONS AUTOMATIC TAGS::= BEGIN

	MyPDU ::= SEQUENCE {
        a1  INTEGER (MyRange),
        a2 OCTET STRING (SIZE(MyRange))
    }
	MyRange::= INTEGER(1..20)
	pdu1 MyPDU ::= {a1 4, a2 'AFBC4583'H}
	
END


--TCLS     MyRange[] MyPDU[]
--TCLS     MyRange[] MyPDU[] {a1[], a2[] }
