-- RUN_SPARK
TEST-CASE DEFINITIONS AUTOMATIC TAGS::= BEGIN

	MyPDU ::= BOOLEAN
	
	pdu1 MyPDU ::= TRUE
	
END


--TCLS     MyPDU[true-value '001'B, false-value '000'B]
--TCLFC    MyPDU[false-value ''B] $$$ sample1.acn:4:6: error: The length of the 'false-value' property must be greater than 0
--TCLFC    MyPDU[true-value ''B] $$$ sample1.acn:4:6: error: The length of the 'true-value' property must be greater than 0
--TCLFC    MyPDU[true-value ''B, false-value ''B] $$$ sample1.acn:4:6: error: The length of the 'true-value' and 'false-value' properties must be greater than 0
--TCLFC    MyPDU[true-value '001'B, false-value '000000'B] $$$ sample1.acn:4:6: error: The length of the 'true-value' and 'false-value' properties must be the same
--TCLFC    MyPDU[true-value '001'B, false-value '001'B] $$$ sample1.acn:4:6: error: The 'true-value' and 'false-value' properties must have different values
