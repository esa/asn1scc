-- ACNV2_ONLY C_ADA_ONLY (the mapping functions are in C and Ada: <name>.helpers)
-- BIT STRING variant of 004: a mapped length determinant sizes a
-- parameterized CHOICE of BIT STRING CONTAINING alternatives.
TEST-CASE DEFINITIONS AUTOMATIC TAGS ::= BEGIN

Document ::= SEQUENCE {
    payload Payload
}

Payload ::= CHOICE {
    value BIT STRING (CONTAINING Value),
    other BIT STRING (CONTAINING Value)
}

Value ::= SEQUENCE {
    number INTEGER (0..255)
}

END

--TCFS   010.acn
