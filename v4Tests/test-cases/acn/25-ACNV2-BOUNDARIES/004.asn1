-- ACNV2_ONLY C_ADA_ONLY (the mapping functions are in C and Ada: <name>.helpers)
-- A mapped length determinant sizes a parameterized CHOICE. Encoding must
-- measure the selected alternative, apply the mapping, and patch the field.
TEST-CASE DEFINITIONS AUTOMATIC TAGS ::= BEGIN

Document ::= SEQUENCE {
    payload Payload
}

Payload ::= CHOICE {
    value OCTET STRING (CONTAINING Value),
    other OCTET STRING (CONTAINING Value)
}

Value ::= SEQUENCE {
    number INTEGER (0..255)
}

END

--TCFS   004.acn
