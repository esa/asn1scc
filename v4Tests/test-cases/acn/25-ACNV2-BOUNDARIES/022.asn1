-- C_ADA_ONLY (Python, Rust: the round trip of the BIT STRING CONTAINING value OuterBits fails: the region of the size deduced contents is not bounded)
--TCFS   022.acn
-- An external determinant must not extend a CONTAINING region past the input.
TEST-CASE DEFINITIONS AUTOMATIC TAGS ::= BEGIN

OuterOct ::= SEQUENCE {
    body OCTET STRING (CONTAINING Inner)
}

OuterBits ::= SEQUENCE {
    body BIT STRING (CONTAINING Inner)
}

Inner ::= SEQUENCE {
    data OCTET STRING (SIZE (0..31))
}

END
