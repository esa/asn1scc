-- KNOWN_FAILURE(python): the Python backend encodes Wrap1 / Mid in methods of their own that take the size parameter by value, while the contents were encoded into a buffer of the caller (NameError: arr)
-- Issue 78: an OCTET STRING (CONTAINING X) component of a SEQUENCE whose size is an ACN parameter of that SEQUENCE
-- (`Wrap1 <INTEGER:len> [] { p [size len] }`, the field passed by the parent: `w <len>`). Before the fix acn-v2
-- never wrote the field (it stayed 0, the decoder ignored it: the round trip passed with a wrong wire format) and
-- legacy stopped with KeyNotFoundException. scripts/runWireTests.sh checks the exact bytes in both modes
-- (037_wire_test.c). The CHOICE form of the pattern (a CONTAINING alternative of a parameterized CHOICE) is
-- tested by 004 / 009 / 010 / 012 / 031; the SEQUENCE as an alternative of a CHOICE by 038 (acn-v2 only).
TEST-CASE DEFINITIONS AUTOMATIC TAGS::= BEGIN

Inner ::= SEQUENCE {
    a INTEGER (0..255),
    b INTEGER (0..3)
}

-- the region between other components, off a byte boundary
Wrap1 ::= SEQUENCE {
    x INTEGER (0..7),
    p OCTET STRING (CONTAINING Inner),
    y BOOLEAN
}

Msg1 ::= SEQUENCE {
    flag INTEGER (0..7),
    w    Wrap1
}

-- the parameter passed on through two levels
Mid ::= SEQUENCE {
    p OCTET STRING (CONTAINING Inner)
}

Wrap2 ::= SEQUENCE {
    m Mid
}

Msg2 ::= SEQUENCE {
    w Wrap2
}

-- an OPTIONAL region, present when a second parameter says so
Wrap4 ::= SEQUENCE {
    p OCTET STRING (CONTAINING Inner) OPTIONAL
}

Msg4 ::= SEQUENCE {
    w Wrap4
}

END

--TCFS   037.acn
