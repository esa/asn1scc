--RUN_SPARK
TEST-CASE DEFINITIONS AUTOMATIC TAGS::= BEGIN

	MyPDU ::= IA5String(SIZE(1..20))
	
	pdu1 MyPDU ::= "George Mamais"
	
END


--TCLFC    MyPDU[size 20]               $$$ sample1.acn:4:6: error: The size constraints of the ASN.1  allows variable items (1 .. 20). Therefore, you should either remove the size property (in which case the size determinant will be encoded automatically exactly like uPER), or use a an Integer field as size determinant
--TCLS     MyPDU[]
--TCLFC    MyPDU[size null-terminated]               $$$ sample1.asn1:4:11: error: 'size null-terminated' on string types requires 'encoding ASCII'
