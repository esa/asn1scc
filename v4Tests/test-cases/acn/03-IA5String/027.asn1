-- A string subtype with ACN 'encoding ASCII' and an external size field that shares the longer typedef of its base
-- type (see 026): the Ada calls take only the subtype's characters + 1.
TEST-CASE DEFINITIONS AUTOMATIC TAGS::= BEGIN

   Str ::= IA5String (SIZE(1..10))
   SubExt ::= Str (SIZE(1..3))

   MyPDU ::= SEQUENCE {
      s      SubExt,
      last   BOOLEAN
   }

END

--TCFS     027.acn
