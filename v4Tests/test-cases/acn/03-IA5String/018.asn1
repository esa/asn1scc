--RUN_SPARK
TEST-CASE DEFINITIONS AUTOMATIC TAGS::= BEGIN

	MyPDU ::= SEQUENCE {
       a1 INTEGER,
       a2 IA5String(SIZE(1..20))(FROM("A".."Z"|"a".."z"|" "|{lf})),
	   a3 IA5String(SIZE(1..20))(FROM("ABCDEFG"))
    }
	
	pdu1 MyPDU ::= {a1 13, a2 {lf, "Hello", lf, "World"}, a3 "ABBBB"}
	
END

--TCLS     MyPDU[]
