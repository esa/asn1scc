--RUN_SPARK
TEST-CASE DEFINITIONS AUTOMATIC TAGS::= BEGIN

	MyPDU ::= IA5String(SIZE(1..20))(FROM("A".."Z"|"a".."z"|" "))
	pdu1 MyPDU ::= "George Mamais       "
	
END

-- ASCII encodings
--TCLS     MyPDU[encoding ASCII]
--TCLS     MyPDU[encoding ASCII, size null-terminated]

-- char index encodings
--TCLS     MyPDU[]
