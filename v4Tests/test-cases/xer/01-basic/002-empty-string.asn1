--NOCOVERAGE
TEST-CASE DEFINITIONS AUTOMATIC TAGS ::= BEGIN

TYPE1 ::= SEQUENCE {
    id1  IA5String (SIZE(0..50)),
    id2  IA5String (SIZE(0..10))
}

TYPE2 ::= SEQUENCE {
    id3 INTEGER (0..256),
    id4 INTEGER (0..65536)
}

TEST-CHOICE ::= CHOICE {
    element1 TYPE1,
    element2 TYPE2
}

LIST-OF-CHOICE ::= SEQUENCE SIZE(3) OF TEST-CHOICE

END
