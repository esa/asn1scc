SCALED DEFINITIONS AUTOMATIC TAGS ::= BEGIN

    -- scaled-integer REAL encodings: the ICD prints the mapping coefficients
    -- exactly (shortest round-trip form), PR #436
    DeltaAngle   ::= REAL (-0.25 .. 0.25)   -- 32 bits: scale 0.5/(2^32-1)
    GnssAccuracy ::= REAL (0.0 .. 655.35)   -- 16 bits: scale 0.01
    BodyRate     ::= REAL (-450.0 .. 450.0)
    Ratio        ::= REAL (0.0 .. 1.0)      -- 8 bits: scale 1/255

    MyPDU ::= SEQUENCE {
        angle   DeltaAngle,
        acc     GnssAccuracy,
        rate    BodyRate,
        fill    Ratio
    }

END
