D DEFINITIONS ::=
BEGIN
 T1  ::= SEQUENCE {
    a INTEGER (1..20) OPTIONAL,
    b INTEGER OPTIONAL,
    c REAL OPTIONAL,
    d REAL
 }
 T2 ::= T1 (WITH COMPONENTS { a ABSENT, b PRESENT })
 
 MySuperSeq ::= SEQUENCE {
	child1 T2,
	child2 REAL
 }

END
