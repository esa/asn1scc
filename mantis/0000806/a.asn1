D DEFINITIONS ::= BEGIN
  T1 ::= SEQUENCE { 
    a SEQUENCE (SIZE (1..10)) OF BOOLEAN OPTIONAL 
  }
  
  T2 ::= T1 (WITH COMPONENTS { a ABSENT })
  
  OCT1 ::= OCTET STRING (SIZE(1..10))
  OCT2 ::= OCTET STRING (SIZE(20))
  STR1 ::= IA5String (SIZE(30))
  STR2 ::= IA5String (SIZE(1..30))
  STR3 ::= IA5String (SIZE(1..30))(FROM("A" .. "Z"))
  
END
