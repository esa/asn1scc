--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-11-6 DEFINITIONS AUTOMATIC TAGS ::= BEGIN
EXPORTS ALL;
IMPORTS
    TimeWindow FROM TimeWindow
    PUSC-UINT32 FROM BasicTypes
    SubSchedule-ID FROM SubSchedule
    Group-ID FROM Group;

maxTC-11-6-Group-ID-Count INTEGER ::= 4095
maxTC-11-6-SubSchedule-ID-Count INTEGER ::= 4095

TC-11-6-DeleteTheTimeBasedScheduledActivitiesIdentifiedByAFilter ::= TC-11-6-DeleteTheTimeBasedScheduledActivitiesIdentifiedByAFilterGeneric {TimeWindow} (WITH COMPONENTS
{
    subschedules PRESENT,
    groups PRESENT
})

TC-11-6-DeleteTheTimeBasedScheduledActivitiesIdentifiedByAFilterGeneric {TimeWindowType} ::= SEQUENCE
{
    timeWindow TimeWindowType,
    subschedules TC-11-6-SubSchedules OPTIONAL,
    groups TC-11-6-Groups OPTIONAL
}

TC-11-6-SubSchedules ::= TC-11-6-SubSchedulesGeneric {SubSchedule-ID}
TC-11-6-Groups ::= TC-11-6-GroupsGeneric {Group-ID}

TC-11-6-SubSchedulesGeneric {SubSchedule-ID-Type} ::= SEQUENCE
{
--! n1 UnsignedInteger,
    subschedule-ID SEQUENCE (SIZE(0 .. maxTC-11-6-SubSchedule-ID-Count)) OF SubSchedule-ID-Type
}

TC-11-6-GroupsGeneric {Group-ID-Type} ::= SEQUENCE
{
--! n2 UnsignedInteger,
    subschedule-ID SEQUENCE (SIZE(0 .. maxTC-11-6-Group-ID-Count)) OF Group-ID-Type
}

END
