--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-6-11 DEFINITIONS AUTOMATIC TAGS ::= BEGIN
EXPORTS ALL;
IMPORTS
    Memory-ID FROM Memory
    BytePointer FROM RawMemory
    PUSC-UINT32 FROM BasicTypes;

TC-6-11-LoadARawMemoryAtomicDataAreaInANonInterruptableTransaction
    ::= TC-6-11-LoadARawMemoryAtomicDataAreaInANonInterruptableTransactionGeneric {BytePointer,
                                                                                   BitMask,
                                                                                   DataToLoad}

TC-6-11-LoadARawMemoryAtomicDataAreaInANonInterruptableTransactionMultipleMemid
    ::= TC-6-11-LoadARawMemoryAtomicDataAreaInANonInterruptableTransactionGeneric {BytePointer,
                                                                                   BitMaskMultipleMemid,
                                                                                   DataToLoadMultipleMemid}

TC-6-11-LoadARawMemoryAtomicDataAreaInANonInterruptableTransactionGeneric
    {UnsignedInteger-Type, BitMask-Type, DataToLoad-Type} ::= SEQUENCE
{
--! memory-ID TMemory-ID, moved to acn
    startAddress UnsignedInteger-Type,
    bitMask BitMask-Type,
    dataToLoad DataToLoad-Type
}

BitMaskMultipleMemid ::= CHOICE
{
    memId1 OCTET STRING (SIZE(4))
}

DataToLoadMultipleMemid ::= CHOICE
{
    memId1 OCTET STRING (SIZE(4))
}

BitMask ::= OCTET STRING (SIZE(4))
DataToLoad ::= OCTET STRING (SIZE(4))

END
