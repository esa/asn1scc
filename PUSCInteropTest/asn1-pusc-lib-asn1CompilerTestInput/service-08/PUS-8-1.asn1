--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-8-1 DEFINITIONS AUTOMATIC TAGS ::= BEGIN
EXPORTS ALL;
IMPORTS
    PUSC-UINT32 FROM BasicTypes;

maxTC-8-1-ArgumentCount INTEGER ::= 4096
maxTC-8-1-Function-ID-Size INTEGER ::= 4

TC-8-1-PerformAFunction ::= TC-8-1-PerformAFunctionGeneric {FunctionArguments}

Argument ::= ArgumentGeneric {ArgumentValue}

TC-8-1-PerformAFunctionGeneric {FunctionArguments-Type} ::= SEQUENCE
{
--! function-ID FixedCharacterString-Type, moved to acn
    functionArguments FunctionArguments-Type
}

Function-ID ::= IA5String (SIZE(maxTC-8-1-Function-ID-Size))

FunctionArguments ::= CHOICE
{
    function0 MultipleArguments,
    function1 INTEGER (0 .. 255)
}

MultipleArguments ::= SEQUENCE
{
--! n PUSC-UINT32, moved to acn
    arguments SEQUENCE (SIZE(1 .. maxTC-8-1-ArgumentCount)) OF Argument
}

ArgumentGeneric {ArgumentValue-Type} ::= SEQUENCE
{
--! argument-ID Argument-ID-Type, moved to acn
    argumentValue ArgumentValue-Type
}

Argument-ID ::= ENUMERATED
{
    arg0 (0)
}

ArgumentValue ::= CHOICE
{
    arg0 INTEGER (0 .. 255)
}


END
