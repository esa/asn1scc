--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-2-4 DEFINITIONS AUTOMATIC TAGS ::= BEGIN
EXPORTS ALL;
IMPORTS
    PUSC-UINT32 FROM BasicTypes;

maxTC-2-4-CpduCommandsCount INTEGER ::= 255
maxTC-2-4-CpduCount INTEGER ::= 127

TC-2-4-DistributeCpduCommands ::= SEQUENCE
{
--! n2 UnsignedInteger-Type, moved to acn
    cpduCommands SEQUENCE (SIZE(1 .. maxTC-2-4-CpduCommandsCount)) OF CpduCommand
}

TC-2-4-DistrubiteCpduCommands-MultipleCpdu ::= SEQUENCE
{
--! n1 UnsignedInteger-Type, moved to acn
    cpdu SEQUENCE (SIZE (1 .. maxTC-2-4-CpduCount)) OF CPDU
}

CPDU ::= CPDU-Generic {CPDU-ID}

CPDU-Generic {CPDU-ID-Type} ::= SEQUENCE
{
    cpdu-ID CPDU-ID-Type,
--! n2 UnsignedInteger-Type, moved to acn
    cpduCommands SEQUENCE (SIZE(1 .. maxTC-2-4-CpduCommandsCount)) OF CpduCommand
}

CpduCommand ::= CpduCommandGeneric {OutputLine-ID}

CpduCommandGeneric {OutputLine-ID-Type} ::= SEQUENCE
{
    outputLine-ID OutputLine-ID-Type,
    reserved BIT STRING (SIZE(1)),
    durationExponentialValue INTEGER (0 .. 7)
}

CPDU-ID ::= ENUMERATED
{
    cpdu0 (0)
}

OutputLine-ID ::= ENUMERATED
{
    out1 (1)
}

END
