--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-2-10 DEFINITIONS AUTOMATIC TAGS ::= BEGIN
EXPORTS ALL;
IMPORTS
    PUSC-UINT32 FROM BasicTypes
    LogicalDevice-ID FROM LogicalDevice;

maxTC-2-10-LogicalDeviceCommandCount INTEGER ::= 63

TC-2-10-DistributeLogicalDeviceCommands ::= SEQUENCE
{
--! n UnsignedInteger-Type, moved to acn
    logicalDeviceCommands SEQUENCE (SIZE(1 .. maxTC-2-10-LogicalDeviceCommandCount)) OF LogicalDeviceCommand
}

LogicalDeviceCommand ::= LogicalDeviceCommandGeneric {Command}

LogicalDeviceCommandGeneric {Command-Type} ::= SEQUENCE
{
--! logicalDevice-ID LogicalDevice-ID-Type, moved to acn
    command Command-Type
}

Command ::= CHOICE
{
    ldev1 Ldev1
}

Ldev1 ::= SEQUENCE
{
--! command-ID Ldev1-Commands, moved to acn
    commandArguments Ldev1-Arguments
}

Ldev1-Commands ::= ENUMERATED
{
    command1 (0)
}

Ldev1-Arguments ::= CHOICE
{
    command1 INTEGER (0 .. 255)
}

END
