--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-12-25 DEFINITIONS AUTOMATIC TAGS ::= BEGIN
EXPORTS ALL;
IMPORTS
    FMON-ID FROM FMON
    PUSC-UINT32 FROM BasicTypes;

maxTC-12-25-FMON-ID-Count INTEGER ::= 4095

TC-12-25-ReportFunctionalMonitoringDefinitions ::= TC-12-25-ReportFunctionalMonitoringDefinitionsGeneric {FMON-ID}

TC-12-25-ReportFunctionalMonitoringDefinitionsGeneric {FMON-ID-Type} ::= SEQUENCE
{
--! n UnsignedInteger,
    fmon-ID SEQUENCE (SIZE(1 .. maxTC-12-25-FMON-ID-Count)) OF FMON-ID-Type
}

END
