--!
--! Copyright (C) 2017-2023 N7 Space sp. z o. o.
--! Contact: https://n7space.com
--!
--! This file is part of ASN.1/ACN PUS-C Components Library.
--!
--! Library was developed under a programme and funded by
--! European Space Agency.
--!
--! This Library is free software: you can redistribute it and/or modify
--! it under the terms of the GNU General Public License as published by
--! the Free Software Foundation, either version 3 of the License, or
--! (at your option) any later version.
--!
--! This Library is distributed in the hope that it will be useful,
--! but WITHOUT ANY WARRANTY; without even the implied warranty of
--! MERCHANTABILITY or FITNESS FOR A PARTICULAR PURPOSE.  See the
--! GNU General Public License for more details.
--!
--! You should have received a copy of the GNU General Public License
--! along with this program.  If not, see <http://www.gnu.org/licenses/>.
--!

PUS-3-30 DEFINITIONS AUTOMATIC TAGS ::= BEGIN
EXPORTS ALL;
IMPORTS
    DiagnosticParameterReportStructure-ID FROM DiagnosticParameterReportStructure
    Parameter-ID FROM Parameter
    PUSC-UINT32 FROM BasicTypes;

maxTC-3-30-Parameter-ID-Count INTEGER ::= 255
maxTC-3-30-SuperComutatedParameterSetCount INTEGER ::= 127

TC-3-30-AppendParametersToADiagnosticParameterReportStructure ::= TC-3-30-AppendParametersToADiagnosticParameterReportStructureGeneric {DiagnosticParameterReportStructure-ID, Parameter-ID} 

TC-3-30-AppendParametersToADiagnosticParameterReportStructureGeneric {DiagnosticParameterReportStructure-ID-Type, Parameter-ID-Type} ::= SEQUENCE
{
    diagnosticParameterReportStructure-ID DiagnosticParameterReportStructure-ID,
--! n1 UnsignedInteger-Type, moved to acn
    parameter-ID SEQUENCE (SIZE(0 .. maxTC-3-30-Parameter-ID-Count)) OF Parameter-ID-Type,
--! nfa UnsignedInteger-Type, moved to acn
    superCommutatedParameterSet SEQUENCE (SIZE(0 .. maxTC-3-30-SuperComutatedParameterSetCount)) OF TC-3-30-SuperCommutatedParameterSet
}

TC-3-30-SuperCommutatedParameterSet ::= TC-3-30-SuperCommutatedParameterSetGeneric {PUSC-UINT32, Parameter-ID}

TC-3-30-SuperCommutatedParameterSetGeneric {UnsignedInteger-Type, Parameter-ID-Type} ::= SEQUENCE
{
    superCommutatedSampleRepetitionNumber UnsignedInteger-Type,
--! n2 UnsignedInteger-Type, moved to acn
    parameter-ID SEQUENCE (SIZE(0 .. maxTC-3-30-Parameter-ID-Count)) OF Parameter-ID-Type
}

END
