CCSDS-SPACE-PACKET DEFINITIONS ::=
BEGIN

ROOT-EMPTY ::= SEQUENCE {}
ROOT-APPLICATION-PROCESS-ID ::= INTEGER(0..2047)
ROOT-PACKET-SEQUENCE-COUNT ::= INTEGER(0..16383)
ROOT-PACKET-DATA-LENGTH ::= INTEGER(0..65535)
ROOT-TIME-REFERENCE-STATUS ::= INTEGER(0..15)
ROOT-MESSAGE-TYPE-COUNTER ::= INTEGER(0..65535)
ROOT-APPLICATION-PROCESS-USER-ID ::= INTEGER(0..65535)
TYPE-ID ::= INTEGER(0..255)
TELEMETRY-SECONDARY-HEADER-PRESENCE-FLAG ::= INTEGER(0..1)
ROOT-PACKET-ERROR-CONTROL ::= INTEGER (0..65535)
ROOT-BOOLEAN ::= BOOLEAN
ROOT-UINT8 ::= INTEGER(0..255)
ROOT-UINT16 ::= INTEGER(0..65535)
ROOT-UINT32 ::= INTEGER(0..4294967295)
ROOT-UINT64 ::= INTEGER(0..18446744073709551615)
ROOT-STRING ::= IA5String (SIZE(0..128))
ROOT-REAL ::= REAL(0.0 .. 10000000.0)
ROOT-STRING-SEQUENCE-OF ::= SEQUENCE (SIZE(0..255)) OF ROOT-STRING
ROOT-BOOLEAN-SEQUENCE-OF ::= SEQUENCE (SIZE(0..255)) OF ROOT-BOOLEAN
ROOT-UINT32-SEQUENCE-OF ::= SEQUENCE (SIZE(0..255)) OF ROOT-UINT32
ROOT-ENDIANNESS ::= ENUMERATED {
   endianness-big (0),
   endianness-little (1)
}

ROOT-PACKET-VERSION-NUMBER ::= ENUMERATED {
   ccsds-packet (0)
}
ROOT-PACKET-TYPE ::= ENUMERATED {
   telemetry (0),
   telecommand (1)
}
ROOT-SECONDARY-HEADER-FLAG ::= BOOLEAN
ROOT-PACKET-ID ::= SEQUENCE {
   packet-type ROOT-PACKET-TYPE,
   secondary-header-flag ROOT-SECONDARY-HEADER-FLAG,
   application-process-id ROOT-APPLICATION-PROCESS-ID
}

ROOT-SEQUENCE-FLAGS ::= ENUMERATED {
   standalone-packet (3)
}
ROOT-PACKET-SEQUENCE-CONTROL ::= SEQUENCE {
   sequence-flags ROOT-SEQUENCE-FLAGS,
   packet-sequence-count ROOT-PACKET-SEQUENCE-COUNT
}
ROOT-REQUEST-ID ::= SEQUENCE {
   packet-version-number ROOT-PACKET-VERSION-NUMBER,
   packet-id ROOT-PACKET-ID,
   packet-sequence-control ROOT-PACKET-SEQUENCE-CONTROL
}

ROOT-ROUTING-FAILURE-NOTICE-CODE ::= ENUMERATED {
   unknown-routing-failure (1)
}
ROOT-ROUTING-FAILURE-NOTICE-DATA ::= CHOICE {
   unknown-routing-failure ROOT-EMPTY
}
ROOT-ROUTING-FAILURE-NOTICE ::= SEQUENCE {
   failure-notice-data ROOT-ROUTING-FAILURE-NOTICE-DATA
}

ROOT-TC-SECONDARY-HEADER ::= SEQUENCE {
   ack-successful-completion   BOOLEAN,
   ack-successful-progress     BOOLEAN,
   ack-successful-start        BOOLEAN,
   ack-successful-acceptance   BOOLEAN,
   source-id                   ROOT-APPLICATION-PROCESS-USER-ID
   -- spare user defined
}

ROOT-TM-SECONDARY-HEADER ::= SEQUENCE {
   time-reference-status       ROOT-TIME-REFERENCE-STATUS,
   message-type-counter        ROOT-MESSAGE-TYPE-COUNTER,
   destination-id              ROOT-APPLICATION-PROCESS-USER-ID
   -- time TODO
   -- spare user defined
}

ROOT-SPACE-PACKET-DATA-FIELD ::= OCTET STRING (SIZE(1..32223))

ROOT-SPACE-PACKET-TELECOMMAND ::= SEQUENCE {
   secondary-header-flag       TELEMETRY-SECONDARY-HEADER-PRESENCE-FLAG,
   application-process-id      ROOT-APPLICATION-PROCESS-ID,
   packet-sequence-count       ROOT-PACKET-SEQUENCE-COUNT,
   packet-data-field           ROOT-SPACE-PACKET-DATA-FIELD ,
   packet-error-control        ROOT-PACKET-ERROR-CONTROL
}

ROOT-SPACE-PACKET-TELEMETRY ::= SEQUENCE {
   secondary-header-flag       TELEMETRY-SECONDARY-HEADER-PRESENCE-FLAG,
   application-process-id      ROOT-APPLICATION-PROCESS-ID,
   packet-sequence-count       ROOT-PACKET-SEQUENCE-COUNT,
   packet-data-field           ROOT-SPACE-PACKET-DATA-FIELD ,
   packet-error-control        ROOT-PACKET-ERROR-CONTROL
}

END
