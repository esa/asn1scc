--RUN_SPARK
TEST-CASE DEFINITIONS AUTOMATIC TAGS::= BEGIN

	-- scaled REAL fields nested inside a SEQUENCE (issue #339)
	GnssAccuracy ::= REAL (0.0 .. 655.35)
	BodyRate ::= REAL (-450.0 .. 450.0)

	MyPDU ::= SEQUENCE {
		acc		GnssAccuracy,
		rate	BodyRate
	}

END

--TCFS     009.acn
