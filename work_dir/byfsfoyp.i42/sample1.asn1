--RUN_SPARK
TEST-CASE DEFINITIONS AUTOMATIC TAGS::= BEGIN

	MyPDU ::= INTEGER
	
	
END


--TCLS     MyPDU[encoding ASCII, size null-terminated]  
--TCLS     MyPDU[encoding ASCII, size 160]  
--TCLFC    MyPDU[encoding ASCII, size 240]          $$$ sample1.acn:4:6: error: Size must be less than 160
