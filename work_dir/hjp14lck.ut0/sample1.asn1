Standard-Datatypes DEFINITIONS AUTOMATIC TAGS ::=
BEGIN

    EXPORTS ALL;

    Standard-Boolean ::= BOOLEAN

    -- 32 bit unsigned integer
    Unsigned-Integer ::= INTEGER(0..2147483647)
  
    -- 32 bit signed integer
    Signed-Integer ::= INTEGER(-2147483648..2147483647)
 
    -- 32 bit real
    Real-1 ::= REAL(-1.0E95..+1.E95)
 
    -- 64 bit real
    -- Correct value for exponent should be 383
    Real-2 ::= REAL(-1.0E300..+1.E300)

END
Event-Action DEFINITIONS AUTOMATIC TAGS ::=
BEGIN

    EXPORTS ALL;

    Event-Action-Service-Report ::= CHOICE {
        foo INTEGER(0..10)
    }

END
Onboard-Monitoring DEFINITIONS AUTOMATIC TAGS ::=
BEGIN

    EXPORTS ALL;

    IMPORTS
        number-of-onboard-parameters,
        Parameter-ID,
        Parameter-Value,
        On-Board-Time
    FROM Onboard-Parameters;


    Onboard-Monitoring-Service-Report ::= CHOICE {
        transition Check-Transition-Report
    }

    Check-Transition-Report ::= SET SIZE (0..number-of-onboard-parameters) OF Transition-Report
    
    Transition-Report ::= SEQUENCE {
        id Parameter-ID,
        value Parameter-Value,
        limit-crossed Parameter-Value,
        previous-checking-status Checking-Status,
        current-checking-status Checking-Status,
        transition-time On-Board-Time
    }

    Checking-Status ::= ENUMERATED {
        witin-limits (0),
        unchecked (1),
        below-low-limit (4),
        above-high-limit (5)
    }

END
Telecommand-Verification DEFINITIONS AUTOMATIC TAGS ::=
BEGIN

    EXPORTS ALL;

    Telecommand-Packet-ID ::= INTEGER(0..10)

    Verification-Failure-Code ::= INTEGER(0..10)

    Telecommand-Verification-Service-Report ::= CHOICE {
        success Successful-Telecommand-Verification-Report,
        failure Failing-Telecommand-Verification-Report
    }

    Successful-Telecommand-Verification-Report ::= SEQUENCE {
        packet-id Telecommand-Packet-ID
    }
    
    Failing-Telecommand-Verification-Report ::= SEQUENCE {
        packet-id Telecommand-Packet-ID,
        code Verification-Failure-Code
    }    

END
Onboard-Parameters DEFINITIONS AUTOMATIC TAGS ::=
BEGIN

    EXPORTS ALL;

    IMPORTS
        Unsigned-Integer
    FROM Standard-Datatypes;

    number-of-onboard-parameters INTEGER ::= 100

    Parameter-ID ::= ENUMERATED {
        voltage-1,
        voltage-2
    }
    
    Parameter-ID-Set ::= SET SIZE (0..number-of-onboard-parameters) OF Parameter-ID 

    Parameter-Value ::= CHOICE {
        type-1-0 Unsigned-Integer,
        type-1-1 Unsigned-Integer
    }
    
    Parameter-Value-Set ::= SET SIZE (0..number-of-onboard-parameters) OF Parameter-Value

    Var-Bit-String ::= SEQUENCE (SIZE(0..8)) OF BOOLEAN
 
    Fixed-Bit-String-1  ::= SEQUENCE (SIZE(1))  OF BOOLEAN
    Fixed-Bit-String-2  ::= SEQUENCE (SIZE(2))  OF BOOLEAN
    Fixed-Bit-String-3  ::= SEQUENCE (SIZE(3))  OF BOOLEAN
    Fixed-Bit-String-4  ::= SEQUENCE (SIZE(4))  OF BOOLEAN
    Fixed-Bit-String-5  ::= SEQUENCE (SIZE(5))  OF BOOLEAN
    Fixed-Bit-String-6  ::= SEQUENCE (SIZE(6))  OF BOOLEAN
    Fixed-Bit-String-7  ::= SEQUENCE (SIZE(7))  OF BOOLEAN
    Fixed-Bit-String-8  ::= SEQUENCE (SIZE(8))  OF BOOLEAN
    Fixed-Bit-String-9  ::= SEQUENCE (SIZE(9))  OF BOOLEAN
    Fixed-Bit-String-10 ::= SEQUENCE (SIZE(10)) OF BOOLEAN
    Fixed-Bit-String-11 ::= SEQUENCE (SIZE(11)) OF BOOLEAN
    Fixed-Bit-String-12 ::= SEQUENCE (SIZE(12)) OF BOOLEAN
    Fixed-Bit-String-13 ::= SEQUENCE (SIZE(13)) OF BOOLEAN
    Fixed-Bit-String-14 ::= SEQUENCE (SIZE(14)) OF BOOLEAN
    Fixed-Bit-String-15 ::= SEQUENCE (SIZE(15)) OF BOOLEAN
    Fixed-Bit-String-16 ::= SEQUENCE (SIZE(16)) OF BOOLEAN
 
    Var-Octet-String ::= OCTET STRING (SIZE(0..8))
 
    Fixed-Octet-String-1  ::= OCTET STRING (SIZE(1))
    Fixed-Octet-String-2  ::= OCTET STRING (SIZE(2))
    Fixed-Octet-String-3  ::= OCTET STRING (SIZE(3))
    Fixed-Octet-String-4  ::= OCTET STRING (SIZE(4))
    Fixed-Octet-String-5  ::= OCTET STRING (SIZE(5))
    Fixed-Octet-String-6  ::= OCTET STRING (SIZE(6))
    Fixed-Octet-String-7  ::= OCTET STRING (SIZE(7))
    Fixed-Octet-String-8  ::= OCTET STRING (SIZE(8))
    Fixed-Octet-String-9  ::= OCTET STRING (SIZE(9))
    Fixed-Octet-String-10 ::= OCTET STRING (SIZE(10))
    Fixed-Octet-String-11 ::= OCTET STRING (SIZE(11))
    Fixed-Octet-String-12 ::= OCTET STRING (SIZE(12))
    Fixed-Octet-String-13 ::= OCTET STRING (SIZE(13))
    Fixed-Octet-String-14 ::= OCTET STRING (SIZE(14))
    Fixed-Octet-String-15 ::= OCTET STRING (SIZE(15))
    Fixed-Octet-String-16 ::= OCTET STRING (SIZE(16))
 
    Var-Character-String ::= OCTET STRING (SIZE(0..100))
 
    Fixed-Character-String-1  ::= OCTET STRING (SIZE(1))
    Fixed-Character-String-2  ::= OCTET STRING (SIZE(2))
    Fixed-Character-String-3  ::= OCTET STRING (SIZE(3))
    Fixed-Character-String-4  ::= OCTET STRING (SIZE(4))
    Fixed-Character-String-5  ::= OCTET STRING (SIZE(5))
    Fixed-Character-String-6  ::= OCTET STRING (SIZE(6))
    Fixed-Character-String-7  ::= OCTET STRING (SIZE(7))
    Fixed-Character-String-8  ::= OCTET STRING (SIZE(8))
    Fixed-Character-String-9  ::= OCTET STRING (SIZE(9))
    Fixed-Character-String-10 ::= OCTET STRING (SIZE(10))
    Fixed-Character-String-11 ::= OCTET STRING (SIZE(11))
    Fixed-Character-String-12 ::= OCTET STRING (SIZE(12))
    Fixed-Character-String-13 ::= OCTET STRING (SIZE(13))
    Fixed-Character-String-14 ::= OCTET STRING (SIZE(14))
    Fixed-Character-String-15 ::= OCTET STRING (SIZE(15))
    Fixed-Character-String-16 ::= OCTET STRING (SIZE(16))
 
    On-Board-Coarse-Time ::= OCTET STRING(SIZE(4))
 
    On-Board-Fine-Time ::= OCTET STRING(SIZE(3))
 
    Time-Component-Rep-Spec ::= INTEGER(0..3)
 
    Time-Rep-Spec ::= SEQUENCE {
       coarse-time-rep Time-Component-Rep-Spec,
       fine-time-rep Time-Component-Rep-Spec
    }

    On-Board-Time ::= SEQUENCE {
       p-field Time-Rep-Spec,
       coarse-time On-Board-Coarse-Time,
       fine-time On-Board-Fine-Time
    }

    Pus-Time ::= On-Board-Time

    Pus-Relative-Time ::= On-Board-Time

END
Event-Reporting DEFINITIONS AUTOMATIC TAGS ::=
BEGIN

    EXPORTS ALL;

    Report-ID ::= INTEGER(0..255)

    Event-Reporting-Service-Report ::= CHOICE {
        normal  Normal-Progress-Report,
        anomaly Error-Anomaly-Report
    }
    
    Normal-Progress-Report ::= SEQUENCE {
        rid Report-ID
    }

    Error-Anomaly-Report ::= CHOICE {
        low     Low-Severity-Error-Anomaly-Report,
        medium  Medium-Severity-Error-Anomaly-Report,
        high    High-Severity-Error-Anomaly-Report
    }

    Low-Severity-Error-Anomaly-Report ::= SEQUENCE {
        rid Report-ID
    }
    Medium-Severity-Error-Anomaly-Report ::= SEQUENCE {
        rid Report-ID
    }
    
    High-Severity-Error-Anomaly-Report ::= SEQUENCE {
        rid Report-ID
    }

END
Service-Reports DEFINITIONS AUTOMATIC TAGS ::=
BEGIN

    EXPORTS ALL;

    IMPORTS
        Event-Reporting-Service-Report FROM Event-Reporting
        Telecommand-Verification-Service-Report FROM Telecommand-Verification
        Onboard-Monitoring-Service-Report FROM Onboard-Monitoring
        Event-Action-Service-Report FROM Event-Action;

    Service-Report ::= CHOICE {
        event-reporting-1 Event-Reporting-Service-Report,
        telecommand-verification-1 Telecommand-Verification-Service-Report,
        onboard-monitoring-1 Onboard-Monitoring-Service-Report,
        event-action-1 Event-Action-Service-Report
    }

END
Onboard-Monitoring-Dataview DEFINITIONS AUTOMATIC TAGS ::=
BEGIN
    
    EXPORTS ALL;
    
    IMPORTS
        Standard-Boolean
    FROM Standard-Datatypes
        Application-Process-ID
    FROM Application-Processes
        number-of-onboard-parameters,
        Parameter-ID,
        Parameter-Value,
        On-Board-Time
    FROM Onboard-Parameters
        Checking-Status,
        Transition-Report
    FROM Onboard-Monitoring;

    Check-State ::= Transition-Report
    
    -- A check transition is really a check state with
    -- current-status != previous-status
    Check-Transition ::= Check-State

    Check-Transition-Set ::= SET SIZE (0..number-of-onboard-parameters) OF Check-Transition

    Check-Definition ::= SEQUENCE {
        lower-bound Parameter-Value,
        upper-bound Parameter-Value
    }

    ---------------------------
    --  Template Parameters  --
    ---------------------------

    monitoring-interval INTEGER ::= 1000
    
    apid Application-Process-ID ::= unit-manager

END
Application-Processes DEFINITIONS AUTOMATIC TAGS ::=
BEGIN

    EXPORTS ALL;

    Application-Process-ID ::= ENUMERATED {
       time-packet(0),
       ground-if(1),
       unit-manager(4),
       packet-router-cdmu(5),
       idle(2047)
    }
 
END
TASTE-Directives DEFINITIONS AUTOMATIC TAGS ::= 
BEGIN

Simulink-Initializer-Excel-T ::= SEQUENCE
{
   filename    IA5String ( SIZE (1 .. 200)),
   col         INTEGER ( 0 .. 200 ),
   line        INTEGER (0 .. 200)
}

Simulink-Script-T ::= SEQUENCE
{
   filename    IA5String ( SIZE (1 .. 200))
}

Taste-directive ::= CHOICE
{
   simulink-initializer-excel Simulink-Initializer-Excel-T,
   simulink-script            Simulink-Script-T
}


END


TEST-CASE DEFINITIONS AUTOMATIC TAGS ::= BEGIN
	-- needed for regression
	MyPDU ::= INTEGER
	pdu1 MyPDU ::= 0
END

--TCFS     03-TERMA.acn
