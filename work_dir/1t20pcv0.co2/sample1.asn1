--RUN_SPARK
TEST-CASE DEFINITIONS AUTOMATIC TAGS::= BEGIN

	MyPDU ::= REAL

	pdu1 MyPDU ::= 3.14159265
	
END

--TCLFC     MyPDU[encoding ASCII]    $$$  sample1.acn:4:6: error: Invalid encoding property value. Expecting 'IEEE754-1985-32', 'IEEE754-1985-64', 'pos-int' or 'twos-complement'
--TCLS     MyPDU[encoding IEEE754-1985-64, endianness little]
--TCLS     MyPDU[encoding IEEE754-1985-64, endianness big]
--TCLS     MyPDU[]
--TCLS     MyPDU[encoding IEEE754-1985-64]
--  TCLS     MyPDU[encoding IEEE754-1985-32]   /*In this test cases the final comparison failes due to conversion from double to float*/


--TCLFC     MyPDU[encoding ASCII, size 100]    $$$  sample1.acn:4:6: error: Invalid encoding property value. Expecting 'IEEE754-1985-32', 'IEEE754-1985-64', 'pos-int' or 'twos-complement'
--TCLFC     MyPDU[encoding pos-int, size 16]    $$$  sample1.acn:4:6: error: REAL types encoded as 'pos-int' or 'twos-complement' must have a closed range constraint (a..b)
