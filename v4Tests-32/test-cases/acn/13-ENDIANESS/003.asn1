TEST-CASE DEFINITIONS AUTOMATIC TAGS::= BEGIN

	MyPDU ::= REAL
	
	pdu1 MyPDU ::= -3.1415
    
	
END

--TCLS     MyPDU[encoding IEEE754-1985-32]
--TCLS     MyPDU[encoding IEEE754-1985-32, endianness big]
--TCLS     MyPDU[encoding IEEE754-1985-32, endianness little]
