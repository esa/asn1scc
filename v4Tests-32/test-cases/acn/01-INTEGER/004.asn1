TEST-CASE DEFINITIONS AUTOMATIC TAGS::= BEGIN

	MyPDU ::= INTEGER
	
	pdu1 MyPDU ::= -687194767
	
END


--TCLFC     MyPDU[encoding ASCII, size 48]       $$$  sample1.acn:4:6: error: The applied ACN encoding does not allow values larger than 99999 to be encoded, while the corresponding ASN.1 type allows values up to 2147483647
--TCLS     MyPDU[]
--TCLFC     MyPDU[encoding ASCII, size -200]     $$$  sample1.acn:4:23: error: no viable alternative at input 'size'

--TCLS     CONSTANT WSIZE ::=32 MyPDU[encoding twos-complement, size WSIZE]
--TCLFC     MyPDU[encoding ASCII, size 81]       $$$  sample1.acn:4:6: error: size value should be multiple of 8
--TCLFC    CONSTANT WSIZE ::=32-1 MyPDU[encoding twos-complement, size WSIZE]      $$$  sample1.acn:4:29: error: The applied ACN encoding does not allow values larger than 1073741823 to be encoded, while the corresponding ASN.1 type allows values up to 2147483647
--TCLFC    MyPDU[encoding pos-int, size 32]          $$$ sample1.acn:4:6: error: Acn property pos-int cannot be applied to signed INTEGER types
