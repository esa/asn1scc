-- It tests the   
-- 'pdu1' does conform to its type constraints. 

TEST-CASE DEFINITIONS AUTOMATIC TAGS::= BEGIN
    
    MyPDU ::= SEQUENCE {
        tap     TAP3File
	}

    TAP3File::=SEQUENCE {
        header  HeaderType,
        data    SourceData
    }

    HeaderType::=SEQUENCE {
        operatorID  IA5String(SIZE(1..10)),
        nrCalls     INTEGER(0..200)
    }
    
    SourceData::=SEQUENCE {
        
        calls   SEQUENCE (SIZE(1..10)) OF Call
    }	

    Call ::= IA5String(SIZE(1..5))
    
	pdu1 MyPDU ::= { tap { 
	                    header{nrCalls 4,operatorID "FA23DF"}, 
	                    data{ calls{"22433","23423","57437","43632"} } 
	                 }
	               }
	
END

--TCFFC     001_00.acn   $$$ sample1.acn:11:22: error: ASN.1 fields cannot act as encoding determinants. Remove field 'nrCalls' from the ASN.1 grammar and introduce it in the ACN grammar
