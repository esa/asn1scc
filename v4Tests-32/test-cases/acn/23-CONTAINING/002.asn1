TEST-CASE DEFINITIONS AUTOMATIC TAGS::= BEGIN

    MyOctet ::= OCTET STRING (SIZE(1..50))

    MySeqType ::= SEQUENCE { 
        a INTEGER (0..255), 
        b INTEGER (0..255)
    }
    
    
	MyContOct ::= OCTET STRING (CONTAINING MySeqType)
    
    MyMasterSeq ::= SEQUENCE {
        a INTEGER (0 .. 200),
        myContOct MyContOct
    }
	
	
END


--TCLS     MyMasterSeq[]
