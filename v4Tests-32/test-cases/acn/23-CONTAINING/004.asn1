TEST-CASE DEFINITIONS AUTOMATIC TAGS::= BEGIN

    MyBitStr ::= BIT STRING (SIZE(1..50))

    
    MySeqType ::= SEQUENCE { 
        a INTEGER (0..255), 
        b INTEGER (0..255)
    }
    
    
	MyPDU ::= BIT STRING (CONTAINING MySeqType)
	
	
END


--TCLS     MyPDU[]
