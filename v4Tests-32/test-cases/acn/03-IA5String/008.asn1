TEST-CASE DEFINITIONS AUTOMATIC TAGS::= BEGIN

	MyPDU ::= IA5String(SIZE(20))
	pdu1 MyPDU ::= "George Mamais       "
	
END

-- ASCII encodings
--TCLS     MyPDU[encoding ASCII, size 20]
--TCLS     MyPDU[encoding ASCII, size null-terminated]

-- char index encodings
--TCLS     MyPDU[]
--TCLS     MyPDU[size 20]
