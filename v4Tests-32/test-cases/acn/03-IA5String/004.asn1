TEST-CASE DEFINITIONS AUTOMATIC TAGS::= BEGIN

	MyPDU ::= SEQUENCE {
       a2 IA5String(SIZE(1..20))(FROM("A".."Z"|"a".."z"|" "))
    }
	
	AT1 ::= INTEGER (1..20)
	
	pdu1 MyPDU ::= {a2 "George Mamais"}
	
END

--TCLS     MyPDU[] { a1 AT1[], a2[size a1]}
