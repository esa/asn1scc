TEST-CASE DEFINITIONS ::= 
BEGIN


-- Input types
Digital-Inputs ::= SEQUENCE {
    sw-cmd BOOLEAN,
    sw-gripper BOOLEAN
}

Analog-Inputs ::= SEQUENCE (SIZE(16)) OF REAL (0.0 .. 6.0)

-- Output types

VR-Model-Output ::= SEQUENCE {
    x1 REAL (-1000 .. 1000),
    y1 REAL(-1000 .. 1000),
    z1 REAL(-1000 .. 1000),
    p1 REAL(-1000 .. 1000),
    x2 REAL(-1000 .. 1000),
    y2 REAL(-1000 .. 1000),
    z2 REAL(-1000 .. 1000),
    p2 REAL(-1000 .. 1000),
    x3 REAL(-1000 .. 1000),
    y3 REAL(-1000 .. 1000),
    z3 REAL(-1000 .. 1000),
    p3 REAL(-1000 .. 1000),
    j-rad SEQUENCE (SIZE(16)) OF REAL (-1000 .. 1000)
}


   	MyPDU ::= SEQUENCE {
        inp1 Digital-Inputs,
        inp2 Analog-Inputs,
        output VR-Model-Output 
    }
	
	pdu1 MyPDU ::=  { inp1 { sw-cmd TRUE, sw-gripper FALSE}, inp2 {0.0, 1.1, 2.2, 3.3, 4.4, 5.5, 0.0, 1.1, 2.2, 3.3, 4.4, 5.5, 0.0, 1.1, 2.2, 3.3},
                        output { x1 -10.0, y1 3.14, z1 0.0, p1 -1000, x2 -10.0, y2 3.14, z2 0.0, p2 -1000, x3 -10.0, y3 3.14, z3 0.0, p3 -1000, 
                        j-rad {0.0, 1.1, 2.2, 3.3, 4.4, 5.5, 0.0, 1.1, 2.2, 3.3, 4.4, 5.5, 0.0, 1.1, 2.2, 3.3} }
    }


END


--TCFS     01-robotic-arm-normal.acn
--TCFS     01-robotic-arm-reverse.acn
