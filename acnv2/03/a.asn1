MyModule DEFINITIONS ::= BEGIN

BUFFER-LENGTH-TYPE ::= INTEGER (0..100)

PDU ::= SEQUENCE {
   hdr  Header,
   payload Payload-t
}

Header ::= SEQUENCE {
   -- empty in ASN.1 (ACN will insert fields here)
}

Payload-t ::= CHOICE {
	case1 PayloadData1,
	case2 PayloadData2
}

PayloadData1 ::= SEQUENCE {
   int-field  INTEGER (-2147483648..2147483647),
   buffer OCTET STRING (SIZE(0..100))
}

PayloadData2 ::= SEQUENCE {
   int-field  INTEGER (-2147483648..2147483647),
   buffer OCTET STRING (SIZE(0..100))
}


END
